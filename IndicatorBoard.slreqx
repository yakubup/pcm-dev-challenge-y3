# IndicatorBoard

## IB 7: CAV Longitudinal Status light is ON when switch is ON and CAV supervisory controller is enabled (Functional)
IB 7: The CAV Longitudinal Control Status light shall be ON when longitudinal control features are allowed and the operator is able to initiate features using other buttons in the vehicle while the longitudinal control system is physically connected to and able to communicate with the CAV supervisory controller.

## IB 1: Propulsion System Status light ON when enabled and no faults are detected (Functional)
IB 1: The Propulsion System light shall be illuminated when any drive mode is enabled and will respond to control inputs. Full torque available. E.g. The driver shifts from parking to drive

## IB 2: Propulsion System Status light OFF when disabled (Functional)
IB 2: The Propulsion System Status light shall be OFF when the vehicle is unable to respond to control inputs.

## IB 3: Propulsion System Status light flashing when faults are detected (Functional)
IB 3: The Propulsion System light shall be flashing when faults are present that prevents the use of the propulsions system.

## IB 4: HV System Status light is ON when battery contractor closed and no isolation faults detected (Functional)
IB 4: The HV System Status light shall be illuminated when the energy storage system contactors are closed and energy storage system is able to provide current to a drive system, without fault, or facilitate on-plug charging. (this includes off and charging conditions)

## IB 5: HV System Status light OFF when battery contactors are open (Functional)
IB 5: The HV System Status light shall be OFF when Energy storage system contactors are open.

## IB 6: HV System Status light flashing when ground fault detected (Functional)
IB 6: The HV System Status light shall be flashing in correspondence to the ground fault indicator. Ground Fault Indicator: illuminated within 60s of when the vehicle ground fault monitor detects a ground fault.

## IB 8: CAV Longitudinal Status light is OFF when switch is OFF (Functional)
IB 8: The CAV Longitudinal Status light is OFF when the operator has put the “CAV Longitudinal Control” switch in the off position.

## IB 9: CAV Longitudinal Status light is flashing when faults detected (Functional)
IB 9: The CAV Longitudinal Status light is flashing when faults are present that prevents the use of any longitudinal control feature.

## IB 10: CAV Lateral Control Status light ON when switch is ON and CAV supervisory control is enabled (Functional)
IB 10: Illuminated when the lateral CAV system is physically connected to and able to communicate with the CSC, i.e. (Lat. control system is enabled and ready to provide the features.). Must be illuminated to initialize any lateral control features.

## IB 11: CAV Lateral Control Status light is OFF when the switch is OFF (Functional)
IB 11: The CAV Lateral Control Status light shall be OFF when the operator has put the “CAV Lateral Control” switch in the off position.

## IB 12: CAV Lateral Control Status light flashing when faults detected (Functional)
IB 12: The CAV Lateral Control Status light shall be flashing when faults are present that prevents the use of any lateral control feature.

## IB 14: CAV V2X Status light OFF when switch is OFF (Functional)
IB 14: The CAV V2X Status light is OFF when the “CAV V2X Control” switch is in the off position.

## IB 15: CAV V2X Status light flashing when faults detected (Functional)
IB 15: The CAV V2X Status light is flashing when faults are present that prevent the use of any V2X data retrieval e.g., disconnected C-V2X radio.

## IB 13: CAV V2X Status light ON when V2X data can be utilized (Functional)
IB 13: The CAV V2X Status light shall be illuminated when use of V2X information for CAV features is allowable.
