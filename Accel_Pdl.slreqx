# Accel_Pdl
Requirements Testing Round

## AP 1: If any of the following situations occur, the arbitrated pedal position must be 0. (Functional)
1. If any of the following situations occur, the arbitrated pedal position must be 0.
- Simultaneous Input of Brake Pedal and Accelerator Pedal Primary is detected
- EDU fault is present
- Accelerator fault is present

## AP 2: If none of these situations occur, the Arbitrated Pedal Position must be equal to Accelerator Pedal Position Primary. (Functional)
2. In the case that none of the following situations occur, the Arbitrated Pedal Position must be equal to Accelerator Pedal Position Primary.
- Simultaneous Input of Brake Pedal and Accelerator Pedal Primary is detected
- EDU fault is present
- Accelerator fault is present

## AP 3: Effective Pedal Position and Actual Pedal Position Must Always Equal Arbitrated Pedal Position (Functional)
3. Effective Pedal Position AND Actual Pedal Position MUST always equal Arbitrated Pedal Position.

## AP 4: 0 torque if accelerator pedal is pressed and the vehicle is in neutral (Functional)
4. 0 torque should be commended if the accelerator pedal is pressed AND the vehicle is in neutral.

## AP 5: 0 torque if accelerator pedal is pressed and vehicle is in park (Functional)
5. 0 torque should be commended if the accelerator pedal is pressed AND the vehicle is in park.

## AP 6: Torque is positive in drive (Functional)
6. When in drive, Torque command must be positive.

## AP 7: Torque is negative in reverse (Functional)
6. When in reverse, Torque command must be negative.

## AP 8: Disagreement fault is 1 if Accelerator Pedal position primary and secondary are different (Functional)
8. The Disagreement fault MUST have a value of 1 if the Accelerator Pedal position primary and Accelerator Pedal position secondary differ.

## AP 9: Primary Out of Range Fault is 1 if Primary Pedal Position is less than 0 or greater than 100 (Functional)
9. The Primary Out of Range Fault MUST have a value of 1 if the Primary pedal position is outside the range 0 – 100.

## AP 10: Secondary Out of Range Fault is 1 if Secondary Pedal Position is less than 0 or greater than 100 (Functional)
10. The Secondary Out Of Range Fault MUST have a value of 1 if the Secondary pedal position is outside the range 0 – 100.

## AP 11: Accelerator Pedal Fault is 1 if any of the faults occur (Functional)
11. The Accelerator Pedal Fault MUST have a value of 1 if any of the faults occur
- Disagreement Fault
- Primary OOR Fault
- Secondary OOR Fault
